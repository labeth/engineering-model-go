package requirements
Requirement REQ_OTA_001 {
  id         = "REQ-OTA-001"
  text       = "Where ota campaign is enabled, when ota campaign scheduled event is received, the ota agent subsystem shall apply the signed firmware bundle to the machine."
  notes      = "Firmware apply behavior; implemented here."
  applies_to = ["FU-OTA-APPLY"]
}
Requirement REQ_OTA_002 {
  id         = "REQ-OTA-002"
  text       = "Where ota campaign is enabled, when ota campaign scheduled event is received, the ota agent subsystem shall verify the firmware signature before apply."
  notes      = "Firmware integrity gate."
  applies_to = ["FU-OTA-VERIFY"]
}
Requirement REQ_OTA_003 {
  id         = "REQ-OTA-003"
  text       = "When firmware validation failed event is received, the ota agent subsystem shall rollback the firmware apply."
  notes      = "Rollback on validation failure."
  applies_to = ["FU-OTA-APPLY"]
}
