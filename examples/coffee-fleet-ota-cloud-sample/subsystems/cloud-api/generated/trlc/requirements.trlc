package requirements
Requirement REQ_CLOUD_001 {
  id         = "REQ-CLOUD-001"
  text       = "Where cloud ingestion is enabled, when telemetry ingested event is received, the cloud api subsystem shall persist a fleet metric."
  notes      = "Telemetry ingestion behavior; implemented here."
  applies_to = ["FU-CLOUD-INGEST"]
}
Requirement REQ_CLOUD_002 {
  id         = "REQ-CLOUD-002"
  text       = "Where cloud ingestion is enabled, when telemetry ingested event is received, the cloud api subsystem shall authenticate the reporting machine."
  notes      = "Ingest authentication control."
  applies_to = ["FU-CLOUD-INGEST"]
}
