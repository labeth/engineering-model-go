package EngineeringModelRequirements
Requirement REQ_EMG_001 {
  id         = "REQ-EMG-001"
  text       = "While local development mode is active, when model updated event is received, the engineering model go shall validate architecture model before generation run is requested."
  notes      = "Validation must gate all generation flows."
  applies_to = ["FU-ASCIIDOC-GENERATOR", "FU-CLI-ORCHESTRATION", "FU-MODEL-LOADER", "FU-OSCAL-EXPORTER", "FU-STRUCTURIZR-EXPORTER", "FU-THREAT-EXPORTER", "FU-VALIDATION-ENGINE"]
}
Requirement REQ_EMG_003 {
  id         = "REQ-EMG-003"
  text       = "While model is valid, when generation run is requested, the engineering model go shall produce AsciiDoc architecture publication output."
  notes      = "Human-readable architecture output remains required."
  applies_to = ["FU-ASCIIDOC-GENERATOR", "FU-CLI-ORCHESTRATION", "FU-VIEW-PROJECTION"]
}
Requirement REQ_EMG_004 {
  id         = "REQ-EMG-004"
  text       = "Where threat export is enabled, when generation run is requested, the engineering model go shall export threat dragon json artifact plus open threat model artifact."
  notes      = "Threat model interchange output contract."
  applies_to = ["FU-CLI-ORCHESTRATION", "FU-THREAT-EXPORTER"]
}
Requirement REQ_EMG_005 {
  id         = "REQ-EMG-005"
  text       = "Where structurizr export is enabled, when generation run is requested, the engineering model go shall export structurizr dsl artifact."
  notes      = "Structurizr DSL is exported for C4 visualization; the exported DSL is validated best-effort by the validate-all gauntlet when a Structurizr validator is available."
  applies_to = ["FU-CLI-ORCHESTRATION", "FU-STRUCTURIZR-EXPORTER"]
}
Requirement REQ_EMG_006 {
  id         = "REQ-EMG-006"
  text       = "Where traceability export is enabled, when generation run is requested, the engineering model go shall produce trlc package and lobster trace report artifacts."
  notes      = "Traceability outputs required for assurance workflows."
  applies_to = ["FU-CLI-ORCHESTRATION", "FU-LOBSTER-EXPORTER", "FU-TRLC-EXPORTER"]
}
Requirement REQ_EMG_007 {
  id         = "REQ-EMG-007"
  text       = "While mcp server is enabled, when mcp tool call is received and catalog references resolve successfully, the engineering model go shall return mcp tool result with schema version and structured error fields."
  notes      = "MCP response contract stability requirement."
  applies_to = ["FU-MCP-SERVER"]
}
Requirement REQ_EMG_008 {
  id         = "REQ-EMG-008"
  text       = "When mcp tool call is received, the engineering model go shall reject path arguments outside repository workspace boundary."
  notes      = "Filesystem trust boundary guardrail."
  applies_to = ["FU-MCP-SERVER"]
}
Requirement REQ_EMG_009 {
  id         = "REQ-EMG-009"
  text       = "While ci validation mode is active, when generation run is requested, the engineering model go shall execute validation plus tests before artifact generated event is raised."
  notes      = "CI gate behavior for deterministic quality."
  applies_to = ["FU-CLI-ORCHESTRATION", "FU-VALIDATION-ENGINE"]
}
Requirement REQ_EMG_010 {
  id         = "REQ-EMG-010"
  text       = "Where requirement trace is complete, when model updated event is received, the engineering model go shall infer traceability coverage from trace markers."
  notes      = "Links runtime, code, and test markers to modeled requirement coverage. Code and metadata scanning excludes dependency caches (node_modules, vendor) and dot-directories (.git, .engmod, tool caches) so coverage reflects only committed first-party source and stays reproducible."
  applies_to = ["FU-CODEMAP-INFERENCE"]
}
Requirement REQ_EMG_011 {
  id         = "REQ-EMG-011"
  text       = "Where external schema dependencies are available, when generation run is requested, the engineering model go shall fail validation if schema checks do not match expected constraints."
  notes      = "Protect export integrity when schema trust fails."
  applies_to = ["FU-STRUCTURIZR-EXPORTER", "FU-THREAT-EXPORTER", "FU-VALIDATION-ENGINE"]
}
Requirement REQ_EMG_012 {
  id         = "REQ-EMG-012"
  text       = "When generation run is requested, the engineering model go shall generate artifacts deterministically so that regeneration is reproducible."
  notes      = "Generation uses stable ordering (sorted diagnostics, link targets, scan results) and excludes environment-specific inputs, so regenerated documents are bit-for-bit reproducible and the CI freshness gate can detect drift."
  applies_to = ["FU-ALLOCATION-TRACE", "FU-ASCIIDOC-GENERATOR", "FU-CODEMAP-INFERENCE"]
}
Requirement REQ_EMG_013 {
  id         = "REQ-EMG-013"
  text       = "Where traceability export is enabled, when generation run is requested, the engineering model go shall export OSCAL SSP plus assessment results plus POA&M artifacts."
  notes      = "OSCAL export set for compliance workflows."
  applies_to = ["FU-CLI-ORCHESTRATION", "FU-OSCAL-EXPORTER"]
}
Requirement REQ_EMG_014 {
  id         = "REQ-EMG-014"
  text       = "Where architecture decision records are authored, when generation run is requested, the engineering model go shall publish architecture decision records document linked from AsciiDoc architecture publication output."
  notes      = "ADRs are first-class model content but are published separately from the main architecture narrative."
  applies_to = ["FU-ASCIIDOC-GENERATOR", "FU-CLI-ORCHESTRATION"]
}
Requirement REQ_EMG_015 {
  id         = "REQ-EMG-015"
  text       = "Where gemara export is enabled, when generation run is requested, the engineering model go shall render OpenSSF Gemara model artifacts."
  notes      = "Gemara is a first-class GRC rendering of the model, validated against the published Gemara schemas via the go-gemara SDK."
  applies_to = ["FU-CLI-ORCHESTRATION", "FU-GEMARA-EXPORTER", "FU-MCP-SERVER"]
}
Requirement REQ_EMG_016 {
  id         = "REQ-EMG-016"
  text       = "Where system composition is enabled, when generation run is requested, the engineering model go shall resolve the subsystem references declared by the parent system from local subdirectory paths."
  notes      = "Recursive system-of-systems composition; local subdirectory references, with external git repositories cloned into the .engmod cache (REQ-EMG-027, ADR-EMG-008, ADR-EMG-010)."
  applies_to = ["FU-MODEL-LOADER", "FU-SYSTEM-COMPOSITION"]
}
Requirement REQ_EMG_017 {
  id         = "REQ-EMG-017"
  text       = "Where system composition is enabled, when generation run is requested, the engineering model go shall reject any subsystem reference that resolves outside the repository workspace boundary."
  notes      = "Downward-only references remain within the workspace; mirrors the MCP path-boundary guardrail."
  applies_to = ["FU-SYSTEM-COMPOSITION"]
}
Requirement REQ_EMG_018 {
  id         = "REQ-EMG-018"
  text       = "Where system composition is enabled, when generation run is requested, the engineering model go shall reject a subsystem reference graph that contains a cycle."
  notes      = "Subsystem references must form a directed acyclic graph (ADR-EMG-009)."
  applies_to = ["FU-SYSTEM-COMPOSITION", "FU-VALIDATION-ENGINE"]
}
Requirement REQ_EMG_019 {
  id         = "REQ-EMG-019"
  text       = "Where system composition is enabled, when generation run is requested, the engineering model go shall resolve cross-system references using subsystem-qualified identifiers."
  notes      = "Identifiers are scoped per system; cross-system references are qualified by subsystem to avoid collisions."
  applies_to = ["FU-ALLOCATION-TRACE", "FU-SYSTEM-COMPOSITION"]
}
Requirement REQ_EMG_020 {
  id         = "REQ-EMG-020"
  text       = "Where system composition is enabled, when generation run is requested, the engineering model go shall materialize parent-to-subsystem allocation traceability in the composed output without modifying any subsystem model."
  notes      = "A subsystem is parent-agnostic; parent allocation is materialized only in composed artifacts, never written back to the child (ADR-EMG-009, ADR-EMG-011)."
  applies_to = ["FU-ALLOCATION-TRACE"]
}
Requirement REQ_EMG_021 {
  id         = "REQ-EMG-021"
  text       = "Where system composition is enabled, when generation run is requested, the engineering model go shall report each subsystem required interface that the parent system does not satisfy."
  notes      = "Subsystems publish a provides-and-requires contract; the parent must satisfy each required interface."
  applies_to = ["FU-ALLOCATION-TRACE", "FU-VALIDATION-ENGINE"]
}
Requirement REQ_EMG_022 {
  id         = "REQ-EMG-022"
  text       = "Where system composition is enabled, when generation run is requested, the engineering model go shall reject an allocation that targets a subsystem identifier not published in the subsystem contract."
  notes      = "Parents may bind only to a subsystem's public contract surface, not its internal identifiers."
  applies_to = ["FU-ALLOCATION-TRACE", "FU-VALIDATION-ENGINE"]
}
Requirement REQ_EMG_023 {
  id         = "REQ-EMG-023"
  text       = "When generation run is requested, the engineering model go shall flag any requirement that links to another requirement in the same document."
  notes      = "Requirements carry no tiers. A requirement is either delegated to a subsystem through a downward composition allocation or implemented here, and the delegation link alone tells the two apart. Linking requirements to one another inside a document recreates tier coupling and is confusing across system boundaries, so it is flagged."
  applies_to = ["FU-ALLOCATION-TRACE", "FU-VALIDATION-ENGINE"]
}
Requirement REQ_EMG_024 {
  id         = "REQ-EMG-024"
  text       = "Where hardware interfaces are authored, when generation run is requested, the engineering model go shall render the hardware to software interface allocation view."
  notes      = "Hardware items and hardware interfaces capture the HW/SW interface (ICD/IRS) for the interface-control view."
  applies_to = ["FU-ASCIIDOC-GENERATOR", "FU-VIEW-PROJECTION"]
}
Requirement REQ_EMG_025 {
  id         = "REQ-EMG-025"
  text       = "Where system composition is enabled, when generation run is requested, the engineering model go shall produce a system requirement allocation matrix aggregated across the composed subsystems."
  notes      = "Aggregate roll-up generation mode for the integrating system."
  applies_to = ["FU-ALLOCATION-TRACE", "FU-ASCIIDOC-GENERATOR"]
}
Requirement REQ_EMG_026 {
  id         = "REQ-EMG-026"
  text       = "Where system composition is enabled, when generation run is requested, the engineering model go shall render in the requirement view the delegation link from each delegated requirement to the specific subsystem requirement that satisfies it."
  notes      = "A provided contract entry names (ref) the subsystem requirement that realizes it, so a parent delegation traces to exactly the requirement that satisfies it. An allocated capability with no such ref is flagged as untraceable, and a ref to a requirement the subsystem does not define is rejected."
  applies_to = ["FU-ALLOCATION-TRACE", "FU-ASCIIDOC-GENERATOR", "FU-VALIDATION-ENGINE"]
}
Requirement REQ_EMG_027 {
  id         = "REQ-EMG-027"
  text       = "Where system composition is enabled, when generation run is requested, the engineering model go shall resolve an external git subsystem reference by cloning the repository into the workspace .engmod cache."
  notes      = "A subsystem may reference an external repository with git (and an optional rev and path). The model is cloned once into .engmod/subsystems/<id> — a gitignored, temporary cache reused while it points at the same repository — and resolved like a local subsystem, giving a full cross-repository composed view. References stay downward-only."
  applies_to = ["FU-MODEL-LOADER", "FU-SYSTEM-COMPOSITION"]
}
Requirement REQ_EMG_028 {
  id         = "REQ-EMG-028"
  text       = "When generation run is requested, the engineering model go shall reject a code trace link that resolves to no requirement or model element."
  notes      = "Code markers (TRLC-LINKS to a requirement, ENGMODEL-LINKS to a model element) are existence-checked against the model, not only shape-checked, so a link to a deleted or mistyped id is a dangling link and fails the build. A trace link is only checked for the model that owns its code (see REQ-EMG-030 scoping)."
  applies_to = ["FU-ALLOCATION-TRACE", "FU-CODEMAP-INFERENCE", "FU-VALIDATION-ENGINE"]
}
Requirement REQ_EMG_029 {
  id         = "REQ-EMG-029"
  text       = "When generation run is requested, the engineering model go shall flag each requirement that is traced by neither code nor verification nor a downward delegation."
  notes      = "An orphan requirement has no implementing code symbol, no verification, and is not delegated to a subsystem; it is a coverage gap surfaced as a warning so it is visible without breaking the build."
  applies_to = ["FU-ALLOCATION-TRACE", "FU-VALIDATION-ENGINE"]
}
Requirement REQ_EMG_030 {
  id         = "REQ-EMG-030"
  text       = "When generation run is requested, the engineering model go shall export a machine-readable traceability matrix that links each requirement to its implementing code and verification and delegated subsystem requirement."
  notes      = "One consolidated matrix (JSON) replaces having to read it out of prose and diagrams. Code is attributed to the model whose architecture.yml is its nearest enclosing root, so a parent model never validates or counts a child model's trace links (monorepo scoping)."
  applies_to = ["FU-ALLOCATION-TRACE", "FU-CODEMAP-INFERENCE"]
}
Requirement REQ_EMG_031 {
  id         = "REQ-EMG-031"
  text       = "When requirements delta is received, the engineering model go shall strictly validate requirements delta schema plus stable identifier operation uniqueness."
  notes      = "Version 1 supports add, whole-entity update, and remove operations. Unknown fields, empty operations, duplicate operations, adds of existing IDs, and updates or removals of missing IDs are rejected."
  applies_to = ["FU-MODEL-CHANGE", "FU-MODEL-LOADER"]
}
Requirement REQ_EMG_032 {
  id         = "REQ-EMG-032"
  text       = "While dry run mode is active, when requirements delta is received, the engineering model go shall validate candidate architecture model without modifying requirements document."
  notes      = "The candidate reuses complete-model structural, catalog, EARS, and internal-link validation before any write is permitted."
  applies_to = ["FU-MODEL-CHANGE", "FU-VALIDATION-ENGINE"]
}
Requirement REQ_EMG_033 {
  id         = "REQ-EMG-033"
  text       = "While model is valid, when requirements delta apply is requested, the engineering model go shall atomically replace requirements document."
  notes      = "The YAML AST merger preserves unchanged nodes and comments. Atomic replacement preserves file permissions and refuses a candidate with blocking diagnostics."
  applies_to = ["FU-CLI-ORCHESTRATION", "FU-MODEL-CHANGE", "FU-VALIDATION-ENGINE"]
}
Requirement REQ_EMG_034 {
  id         = "REQ-EMG-034"
  text       = "When requirements delta is received, the engineering model go shall produce deterministic requirements change summary."
  notes      = "The summary sorts added, updated, and removed stable IDs and reports changed fields for whole-entity updates."
  applies_to = ["FU-CLI-ORCHESTRATION", "FU-MODEL-CHANGE"]
}
